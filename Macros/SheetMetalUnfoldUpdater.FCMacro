__author__ = "ceremcem"
"""
Description:

This macro automatically updates all unfold operations as well as their related 
TechDraw views. It depends on some LinkStage3 features, see 
https://github.com/realthunder/FreeCAD_assembly3 for more info.

Usage: 

1. Put your processed object into an assembly container. 
2. Create an "Element" for the unfold face
3. Rename the element to "foo_unfold_face"
4. Run this macro 
5. See "foo_unfold" sketch is created properly. 
6. See any TechDraw ProjGroup source is updated properly
"""

import FreeCAD
import re

echo = FreeCAD.Console.PrintMessage
warn = FreeCAD.Console.PrintWarning
error = FreeCAD.Console.PrintError

prev_workbench = Gui.activeWorkbench().name()
# TODO: Actually there is no need to switch to SMWorkbench after the first one.
Gui.activateWorkbench("SMWorkbench")
if prev_workbench:
	Gui.activateWorkbench(prev_workbench)

doc = App.ActiveDocument
unfold_sketch_regex = re.compile('.+_unfold_face')

echo("--------------------- Updating unfold ------------------------------\n")

for o in doc.Objects:
	try:
		_o = o.TypeId
	except: 
		# probably we deleted this object before updating the existing unfold sketch.
		continue
		
	# find any Asm3 Element that matches with our magic postfix
	if o.TypeId == 'Part::FeaturePython':
		match = unfold_sketch_regex.match(o.Label)
		if match:
			output_name = o.Label[:-5]  # remove the "_face" postfix
			echo("===> Found unfold job: " + output_name + " \n")

			related_views = []
			for x in doc.Objects:
				if x.TypeId == 'TechDraw::DrawPage': 
					for view in x.Views:
						try: 
							_src = view.Source[0]
						except Exception as e:
							continue
						#print "source of ", view.Label, ' in ', x.Label, " is: ", _src.Label
						if _src.Label == output_name:
							# This view uses our unfolded output, update this view at the end 
							echo("* Found related TechDraw ProjGroup: %s\n" % view.Label)
							related_views.append(view)
			
			# mark current output as "to be deleted"
			tmp_postfix = "_TMP"
			old = None		
			try:
				old = doc.getObjectsByLabel(output_name)[0]
				old.Label += tmp_postfix
				doc.recompute()
			except:
				pass
			
			# Select the unfold face (see realthunder/FreeCAD_assembly3#262)
			face_elem = doc.getObjectsByLabel(output_name + '_face')[0].Proxy
			Gui.Selection.clearSelection()
			Gui.Selection.addSelection(face_elem.getAssembly().getPartGroup(), face_elem.getElementSubname(True))

			Gui.runCommand('SMUnfoldUnattended')

			try:
				# Remove unnecessary unfolded solid
				doc.removeObject('Unfold')
				
				# Properly rename the output
				sketch = doc.getObjectsByLabel('Unfold_Sketch')[0]
				sketch.Label = output_name
				sketch.Visibility = False
				
				# Update the source of related views
				if len(related_views) > 0:
					for view in related_views:
						echo("* Updating %s source as %s\n" % (view.Label, sketch.Label))
						view.Source = [sketch]
				else:
					warn('No TechDraw view is updated.\n')

				# remove the temporary object
				if old is not None:
					doc.removeObject(old.Name)
					doc.recompute()
			except Exception as e:
				error('Something went wrong:' )
				error(e)
				error('\n')
				# restore the previous sketch
				if old is not None:
					echo("* Restoring the previous sketch.\n")
					old.Label = old.Label[:-(len(tmp_postfix))]
					doc.recompute()


doc.recompute()
Gui.Selection.clearSelection()
